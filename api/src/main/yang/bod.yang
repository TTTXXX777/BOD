module bod {
    yang-version 1;
    namespace "urn:opendaylight:params:xml:ns:yang:bod";
    prefix "bod";

    import opendaylight-inventory {prefix inv;revision-date "2013-08-19";}

    revision "2015-01-05" {
        description "Initial revision of bod model";
    }

    rpc send-command {
    	input {
    		leaf operation {
    			type string;
    		}
            leaf srcRRU1 {
                type uint8;
            }
            leaf srcRRU2 {
                type uint8;
            }
            leaf dstBBU1 {
                type uint32;
            }
            leaf dstBBU2 {
                type uint32;
            }
    	}
    	output {
    		leaf result {
    			type string;
    		}
    	}
    }
}
